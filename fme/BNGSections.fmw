FME workspace BNGSections.fmw

Parameters:
- SourceDataset_GEOTIFF = C:\Users\obliczenia\map-tiles-tools\input\data\50k\data\**\*.tif   # Source GeoTIFF File(s)
- DestDataset_CSV2 = C:\Users\obliczenia\map-tiles-tools\input\data   # Destination CSV (Comma Separated Value) Folder

Readers:
- GEOTIFF_1: GEOTIFF from $(SourceDataset_GEOTIFF) in EPSG:27700

Writers:
- CSV2_1: CSV2 to $(DestDataset_CSV2)

GEOTIFF (reader GEOTIFF_1)
    -> RasterExtentsCoercer
RasterExtentsCoercer
    EXTENTS_TYPE = Raster Extents
    EXTENTS -> TestFilter
Note: Podział na grupy wg wlasnego uznania, patrzac na mape BNG
TestFilter
    DEFAULT_VALUE = <UNFILTERED>
    TEST_LIST = "BOOL_OP,OR,COMPOSITE_TEST,""""""1"""""",TEST_CLAUSE,CASE_INSENSITIVE_TEST @Left(@Value(fme_basename),2) IN HP,HT,HU,HW,HX,HY,HZ,NA,NB,NC,ND,NF,NG,NH,NJ,NK",group 1,"BOOL_OP,OR,COMPOSITE_TEST,""""""1"""""",TEST_CLAUSE,CASE_INSENSITIVE_TEST @Left(@Value(fme_basename),2) IN NL,NM,NN,NO,NR,NS,NT,NU,NW,NX,NY,NZ",group 2
    group 1 -> AttributeCreator
    group 1 -> SpatialFilter [Filter]
    group 2 -> SpatialFilter [Candidate]
Note: Ustalenie, ktore pliki z drugiej, sasiadujacej grupy stykaja sie z grupa 1.
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
AttributeCreator
    ATTR_TABLE:
      SET_TO fileName = @Value(fme_basename)
      SET_TO filePath = @Value(fme_dataset)
    -> groups (writer CSV2_1)
Note: Zapis do pliku CSV
groups (writer CSV2_1)
    attributes: fileName string, filePath string
