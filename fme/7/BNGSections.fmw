FME workspace BNGSections.fmw

Parameters:
- SourceDataset_GEOTIFF = C:\Users\obliczenia\map-tiles-tools\input\data\250k\**\*.tif   # Source GeoTIFF File(s)
- DestDataset_CSV2 = C:\Users\obliczenia\map-tiles-tools\input\data\groups\7-250   # Destination CSV (Comma Separated Value) Folder

Readers:
- GEOTIFF_1: GEOTIFF from $(SourceDataset_GEOTIFF) in EPSG:27700

Writers:
- CSV2_1: CSV2 to $(DestDataset_CSV2)

GEOTIFF (reader GEOTIFF_1)
    -> RasterExtentsCoercer
RasterExtentsCoercer
    EXTENTS_TYPE = Raster Extents
    EXTENTS -> TestFilter
Note: Podział na grupy wg wlasnego uznania, patrzac na mape BNG
TestFilter
    DEFAULT_VALUE = <UNFILTERED>
    TEST_LIST = "BOOL_OP,OR,COMPOSITE_TEST,""""""1"""""",TEST_CLAUSE,CASE_INSENSITIVE_TEST @Left(@Value(fme_basename),2) IN HP,HT,HU",group 1,"BOOL_OP,OR,COMPOSITE_TEST,""""""1"""""",TEST_CLAUSE,CASE_INSENSITIVE_TEST @Left(@Value(fme_basename),2) IN HW,HX,HY,HZ,NA,NB,NC,ND",group 2,"BOOL_OP,OR,COMPOSITE_TEST,""""""1"""""",TEST_CLAUSE,CASE_INSENSITIVE_TEST @Left(@Value(fme_basename),2) IN NF,NG,NH,NJ,NK,NL,NM,NN,NO",group 3,"BOOL_OP,OR,COMPOSITE_TEST,""""""1"""""",TEST_CLAUSE,CASE_INSENSITIVE_TEST @Left(@Value(fme_basename),2) IN NR,NS,NT,NU,NW,NX,NY,NZ,OV",group 4,"BOOL_OP,OR,COMPOSITE_TEST,""""""1"""""",TEST_CLAUSE,TEST @Left(@Value(fme_basename),2) IN SC,SD,SE,TA,SH,SJ,SK,TF,TG",group 5,"BOOL_OP,OR,COMPOSITE_TEST,""""""1"""""",TEST_CLAUSE,TEST @Left(@Value(fme_basename),2) IN SM,SN,SO,SP,TL,TM,SR,SS,ST,SU,TQ,TR",group 6,"BOOL_OP,OR,COMPOSITE_TEST,""""""1"""""",TEST_CLAUSE,TEST @Left(@Value(fme_basename),2) IN SV,SW,SX,SY,SZ,TV",group 7
    group 1 -> AttributeCreator
    group 1 -> SpatialFilter [Filter]
    group 1 -> SpatialFilter_2 [Candidate]
    group 2 -> SpatialFilter [Candidate]
    group 2 -> AttributeCreator_2
    group 2 -> SpatialFilter_2 [Filter]
    group 2 -> SpatialFilter_3 [Candidate]
    group 3 -> SpatialFilter_3 [Filter]
    group 3 -> AttributeCreator_3
    group 3 -> SpatialFilter_2 [Candidate]
    group 3 -> SpatialFilter_4 [Candidate]
    group 4 -> AttributeCreator_4
    group 4 -> SpatialFilter_4 [Filter]
    group 4 -> SpatialFilter_5 [Candidate]
    group 4 -> SpatialFilter_3 [Candidate]
    group 5 -> AttributeCreator_5
    group 5 -> SpatialFilter_4 [Candidate]
    group 5 -> SpatialFilter_5 [Filter]
    group 5 -> SpatialFilter_6 [Candidate]
    group 6 -> AttributeCreator_6
    group 6 -> SpatialFilter_5 [Candidate]
    group 6 -> SpatialFilter_6 [Filter]
    group 6 -> SpatialFilter_7 [Candidate]
    group 7 -> AttributeCreator_7
    group 7 -> SpatialFilter_6 [Candidate]
    group 7 -> SpatialFilter_7 [Filter]
Note: Ustalenie, ktore pliki z drugiej, sasiadujacej grupy stykaja sie z grupa 1.
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator
AttributeCreator
    ATTR_TABLE:
      SET_TO fileName = @Value(fme_basename)
      SET_TO filePath = @Value(fme_dataset)
    -> group1 (writer CSV2_1)
    -> Inspector
Note: Zapis do pliku CSV
group1 (writer CSV2_1)
    attributes: fileName string, filePath string
Inspector
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_2
AttributeCreator_2
    ATTR_TABLE:
      SET_TO fileName = @Value(fme_basename)
      SET_TO filePath = @Value(fme_dataset)
    -> group2 (writer CSV2_1)
    -> Inspector_2
group2 (writer CSV2_1)
    attributes: fileName string, filePath string
Inspector_2
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_3
AttributeCreator_3
    ATTR_TABLE:
      SET_TO fileName = @Value(fme_basename)
      SET_TO filePath = @Value(fme_dataset)
    -> group3 (writer CSV2_1)
    -> Inspector_3
group3 (writer CSV2_1)
    attributes: fileName string, filePath string
Inspector_3
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_4
AttributeCreator_4
    ATTR_TABLE:
      SET_TO fileName = @Value(fme_basename)
      SET_TO filePath = @Value(fme_dataset)
    -> group4 (writer CSV2_1)
    -> Inspector_4
group4 (writer CSV2_1)
    attributes: fileName string, filePath string
Inspector_4
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_5
AttributeCreator_5
    ATTR_TABLE:
      SET_TO fileName = @Value(fme_basename)
      SET_TO filePath = @Value(fme_dataset)
    -> Inspector_5
    -> group5 (writer CSV2_1)
group5 (writer CSV2_1)
    attributes: fileName string, filePath string
Inspector_5
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_6
AttributeCreator_6
    ATTR_TABLE:
      SET_TO fileName = @Value(fme_basename)
      SET_TO filePath = @Value(fme_dataset)
    -> Inspector_6
    -> group6 (writer CSV2_1)
group6 (writer CSV2_1)
    attributes: fileName string, filePath string
Inspector_6
SpatialFilter_7
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> AttributeCreator_7
AttributeCreator_7
    ATTR_TABLE:
      SET_TO fileName = @Value(fme_basename)
      SET_TO filePath = @Value(fme_dataset)
    -> group7 (writer CSV2_1)
    -> Inspector_7
group7 (writer CSV2_1)
    attributes: fileName string, filePath string
Inspector_7
