FME workspace pngraster.fmw

Parameters:
- SourceDataset_PNGRASTER_3 = C:\Users\obliczenia\map-tiles-tools\output\tiles\2\11\**\*.png   # Source PNG (Portable Network Graphics) File(s)
- SourceDataset_GEOTIFF = C:\Users\obliczenia\map-tiles-tools\input\data\250k\**\*.tif   # Source GeoTIFF File(s)

Readers:
- PNGRASTER_2: PNGRASTER from $(SourceDataset_PNGRASTER_3) in EPSG:3857
- GEOTIFF_1: GEOTIFF from $(SourceDataset_GEOTIFF) in EPSG:27700

PNGRASTER (reader PNGRASTER_2)
    -> RasterExtentsCoercer
GEOTIFF (reader GEOTIFF_1) [off]
    -> RasterExtentsCoercer
RasterExtentsCoercer
    EXTENTS_TYPE = Raster Extents
    EXTENTS -> Inspector
Inspector
